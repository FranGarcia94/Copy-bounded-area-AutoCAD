(defun C:AA (/ en ss lst ssall tmp head)
(SETQ cont 0)
(setq lista (entget(car(entsel))))
(setq puntos ())
(WHILE (/= (nth cont lista) (nth 39 lista))
(if (= (car(nth cont lista)) 10)
(setq puntos (append (list (cdr(nth cont lista)))  (list puntos))))
(setq cont (+ cont 1))
)
(setq p1 (car puntos))
(setq p2 (car (car (cdr puntos))))
(setq p3 (car (car (cdr  (car (cdr puntos))))))
(setq p4 (car (car (cdr (car (cdr  (car (cdr puntos))))))))
(setq pt_list (list p1 p2 p3 p4))
(setq conj (ssget "_CP" pt_list))
(COMMAND "_.copyclip" conj "")
(setq conj2 (ssget "_WP" pt_list))
(command "_change" conj2 "" "_p" "_c" "3" "")
)
